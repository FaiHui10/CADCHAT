(defun c:DrawIsoscelesTriangle (/ baseWidth height basePt apexPt leftPt rightPt result)
 (princ "\n命令已加载，输入 DrawIsoscelesTriangle 执行")
 (setq result (vl-catch-all-apply
   (function
     (lambda ()
       (setq basePt (getpoint "\n指定三角形底边中点: "))
       (if (null basePt)
         (princ "\n未指定底边中点，命令取消。")
         (progn
           (setq baseWidth (getdist basePt "\n指定底边长度: "))
           (if (null baseWidth)
             (princ "\n未指定底边长度，命令取消。")
             (progn
               (setq height (getdist basePt "\n指定三角形高度: "))
               (if (null height)
                 (princ "\n未指定高度，命令取消。")
                 (progn
                   (setq apexPt (list (car basePt) (+ (cadr basePt) height) (caddr basePt)))
                   (setq leftPt (list (- (car basePt) (/ baseWidth 2.0)) (cadr basePt) (caddr basePt)))
                   (setq rightPt (list (+ (car basePt) (/ baseWidth 2.0)) (cadr basePt) (caddr basePt)))
                   (command "_.pline" leftPt apexPt rightPt "c")
                   (princ "\n等腰三角形绘制完成！")
                 )
               )
             )
           )
         )
       )
     )
   )
 ))
 (if (vl-catch-all-error-p result)
   (princ (strcat "\n错误: " (vl-catch-all-error-message result)))
 )
 (princ)
)
